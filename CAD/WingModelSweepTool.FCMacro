# Macro to create Prandtl wing geometry using guidesplines

import FreeCAD
import PartDesign
import importAirfoilDAT
import DraftTools
import PartDesignGui
import Part
import Draft
import math

CADdocname = "PrandtlWing"

App.newDocument(CADdocname)

fulltwist = [8.3274,8.5524,8.7259,8.8441,8.903,8.8984,8.8257,8.6801,8.4565,8.1492,7.7522,7.2592,6.6634,5.9579,5.1362,4.1927,3.1253,1.9394,0.6589,-0.6417,-1.6726]
twist = [-fulltwist[0], fulltwist[10], -fulltwist[-1]]

#pathsectionfiles = u"F:/PrandtlVlerk/P4/PrandtlWingFullScale/CAD/"
pathsectionfiles = u"/media/asenna/WitkruisArend/PrandtlVlerk/P2/prandtl2/CAD/"

sectionfiles = ['PRNCENMOD.dat', 'section_10.dat', 'PRNTIPMOD.dat']

b = 2.25 # Span in metres
spanrange = list(range(0,3))
spanrange = [(b/2)*spanpos*1000 for spanpos in spanrange]

sweepangle = 24*math.pi/180 # [radians]
sweeprange = [math.tan(sweepangle)*spanpos for spanpos in spanrange]


rootchord = 240 # [mm]
tipchord = 60 # [mm]

chordrange = [rootchord, (rootchord+tipchord)/2, tipchord]

# Remember to add the dihedral angle
# Add the dihedral angle last to prevent parallellogram of wing.





App.activeDocument().addObject('PartDesign::Body','Body')

for cstation in range(0,3):
	# First import the 2D section
	importAirfoilDAT.insert(pathsectionfiles + sectionfiles[cstation], CADdocname)

	# Now scale the imported section to the chordsize at this spanwise station
	Draft.scale([FreeCAD.ActiveDocument.ActiveObject],delta=FreeCAD.Vector(chordrange[cstation],chordrange[cstation],1.0),center=FreeCAD.Vector(0.0,0.0,0.0),copy=False,legacy=True)
	FreeCAD.ActiveDocument.recompute()

	# Rotate the sketch through the twist angle
	rotatepoint = 0.25*chordrange[cstation]
	Draft.rotate([FreeCAD.ActiveDocument.ActiveObject],twist[cstation],FreeCAD.Vector(rotatepoint,0.0,0.0),axis=FreeCAD.Vector(0.0,0.0,1.0),copy=False)
	# Move the sketch to the correct sweepback position
	Draft.move([FreeCAD.ActiveDocument.ActiveObject],FreeCAD.Vector(sweeprange[cstation],0.0,spanrange[cstation]),copy=False)
	Draft.downgrade(FreeCAD.ActiveDocument.ActiveObject,delete=True)
	Draft.downgrade(FreeCAD.ActiveDocument.ActiveObject,delete=True)
	

FreeCAD.ActiveDocument.recompute()


import Draft

# Leading edge guide spline points
points=[FreeCAD.Vector(1.3573725001,8.6365215677,0),
FreeCAD.Vector(26.3932023093,8.5348851983,56.25),
FreeCAD.Vector(51.4137905962,8.3671718801,112.5),
FreeCAD.Vector(76.4193772461,8.1359540589,168.75),
FreeCAD.Vector(101.4104955587,7.8441684663,225),
FreeCAD.Vector(126.3879905727,7.4951513998,281.25),
FreeCAD.Vector(151.3529968138,7.0925175413,337.5),
FreeCAD.Vector(176.3069946581,6.6403885603,393.75),
FreeCAD.Vector(201.2517994662,6.143364127,450),
FreeCAD.Vector(226.1895217349,5.6063832015,506.25),
FreeCAD.Vector(251.1226225902,5.0350422804,562.5),
FreeCAD.Vector(276.0538984647,4.4356695227,618.75),
FreeCAD.Vector(300.9864305068,3.8152907683,675),
FreeCAD.Vector(325.9235854708,3.1819644872,731.25),
FreeCAD.Vector(350.8689644917,2.5450818824,787.5),
FreeCAD.Vector(375.8262788984,1.9155581784,843.75),
FreeCAD.Vector(400.7992368485,1.3067865678,900),
FreeCAD.Vector(425.7912181487,0.7355183753,956.25),
FreeCAD.Vector(450.8047306452,0.2241686546,1012.5),
FreeCAD.Vector(475.8402219761,-0.1931661952,1068.75),
FreeCAD.Vector(500.8924602621,-0.4377170279,1125)]
Draft.makeWire(points,closed=False,face=False,support=None)


# Trailing edge guide spline points
points=[FreeCAD.Vector(239.3757440853,-22.3278305929,0),
FreeCAD.Vector(255.360175604,-22.2130203618,56.25),
FreeCAD.Vector(271.3621645213,-21.8960058545,112.5),
FreeCAD.Vector(287.3828593276,-21.3845681812,168.75),
FreeCAD.Vector(303.4227621139,-20.6876975176,225),
FreeCAD.Vector(319.4816934107,-19.8157012627,281.25),
FreeCAD.Vector(335.5588224191,-18.7798309996,337.5),
FreeCAD.Vector(351.6525928942,-17.5929761644,393.75),
FreeCAD.Vector(367.760753834,-16.2695653168,450),
FreeCAD.Vector(383.8804455022,-14.8251287397,506.25),
FreeCAD.Vector(400.0081598843,-13.2772501714,562.5),
FreeCAD.Vector(416.1398230261,-11.6457634031,618.75),
FreeCAD.Vector(432.2709514284,-9.9526106745,675),
FreeCAD.Vector(448.3967653165,-8.2228101428,731.25),
FreeCAD.Vector(464.5124218065,-6.4852958017,787.5),
FreeCAD.Vector(480.6134043325,-4.7734046812,843.75),
FreeCAD.Vector(496.6959877968,-3.1276391328,900),
FreeCAD.Vector(512.7580986971,-1.5981649462,956.25),
FreeCAD.Vector(528.8006138495,-0.251576395,1012.5),
FreeCAD.Vector(544.8296525543,0.8111555842,1068.75),
FreeCAD.Vector(560.8621785197,1.355456973,1125)]
Draft.makeWire(points,closed=False,face=False,support=None)
